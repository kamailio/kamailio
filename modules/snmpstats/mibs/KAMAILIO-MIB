-- ***********************************************************************
-- KAMAILIO-MIB:  KAMAILIO MIB
--
-- Date of Creation: Januay 2006
--
-- This MIB provides information related to the Kamailio SIP Router.
-- 
-- Copyright (c) The Internet Society (2006)
-- Ammendments (c) Soma Networks, Inc. (2006)
-- Kamailio extras (c) Edvina AB, 2013
--
-- All rights reserved.
-- *****************************************************************

KAMAILIO-MIB DEFINITIONS ::= BEGIN

    IMPORTS
        MODULE-IDENTITY,
        OBJECT-TYPE, 
        OBJECT-IDENTITY,
        NOTIFICATION-TYPE,
        Integer32,
        Unsigned32,
        Counter32,
        Counter64,
        Gauge32
            FROM SNMPv2-SMI
            
        DateAndTime,
	TEXTUAL-CONVENTION,
	DisplayString,
	RowStatus,
	TruthValue
            FROM SNMPv2-TC

        SnmpAdminString
            FROM SNMP-FRAMEWORK-MIB

        X731UsageState,
        X731AlarmStatus,
        X731AlarmState
            FROM KAMAILIO-TC
            
        MODULE-COMPLIANCE,
        OBJECT-GROUP,
        NOTIFICATION-GROUP
            FROM SNMPv2-CONF

        kamailioModules, kamailioMIB
            FROM KAMAILIO-REG-MIB;

    kamailioModule MODULE-IDENTITY
        LAST-UPDATED "201301081200Z"
        ORGANIZATION "Kamailio"
        CONTACT-INFO 
            "http://www.kamailio.org"
        DESCRIPTION
            "Kamailio MIB module.
             This module defines objects which are neceesary to monitor an
             instance of Kamailio.
             
             The objects in this MIB are intended to be used in conjunction
             with those rovided in KAMAILIO-SIP-COMMON-MIB and
             KAMAILIO-SIP-SERVER-MIB.  In particular, this MIB defines the X.731
             attributes required to monitor the Kamailio subsystems and the
             Kamailio core itself."
        REVISION   "200605021200Z"
        DESCRIPTION
            "clarified some of the statisitcs collected, added the alarm 
            states and notifications."
        REVISION   "200603231200Z"
        DESCRIPTION
           "changed ownership to Kamailio group, and made it SMIv2 compliant."
        REVISION   "200601061200Z"
        DESCRIPTION
           "Initial version of the KAMAILIO-MIB module."
        REVISION   "201301081200Z"
        DESCRIPTION
           "Renamed MIB and mib entries to new product name, Kamailio."
        REVISION   "201303301200Z"
        DESCRIPTION
           "Added Kamailio process information - memory, transports, core configuration"
        ::= { kamailioModules 5 }

--
-- Top-Level Components of this MIB.
--
    kamailioObjects OBJECT-IDENTITY
        STATUS current
        DESCRIPTION 
        "Sub-tree for accessible objects in the MIB."
        ::= { kamailioMIB 1 } 

    kamailioMIBEvents OBJECT-IDENTITY
        STATUS current
        DESCRIPTION
        "A sub-tree for all the KAMAILIO-MIB related events and traps."
        ::= {kamailioMIB 2 }

    kamailioConform OBJECT-IDENTITY
        STATUS current
        DESCRIPTION 
        "Sub-tree for Conformance specifications."
        ::= { kamailioMIB 3 }

--
-- kamailioObjects sub-components
--
    kamailioServer  OBJECT-IDENTITY
        STATUS current
        DESCRIPTION 
        "Sub-tree for Server state, alarms, and management."
        ::= { kamailioObjects 1 }

    kamailioMsgs  OBJECT-IDENTITY
        STATUS current
        DESCRIPTION 
        "Sub-tree for tracking of individual SIP messages processed by Kamailio."
        ::= { kamailioObjects 2 }

   kamailioDialog  OBJECT-IDENTITY
        STATUS current
        DESCRIPTION 
        "Sub-tree for tracking of SIP Dialogs being processed by Kamailio."
    ::= { kamailioObjects 3 }

   kamailioNet OBJECT-IDENTITY
        STATUS current
        DESCRIPTION 
        "Sub-tree for tracking of Network Transports being enabled in Kamailio."
    ::= { kamailioObjects 4 }

-- 
-- Kamailio Server Objects
--
    kamailioSrvMemory OBJECT-IDENTITY
        STATUS current
        DESCRIPTION 
        "Sub-tree for Core Memory Statistics." 
        ::= { kamailioServer 1 }

    kamailioSrvConfig OBJECT-IDENTITY
        STATUS current
        DESCRIPTION 
        "Sub-tree for Core configuration - compile flags etc." 
        ::= { kamailioServer 2 }

    kamailioSrvCounters OBJECT-IDENTITY
        STATUS current
        DESCRIPTION 
        "Sub-tree for Core Counters/Statistic variables." 
        ::= { kamailioServer 3 }

    kamailioSrvProcess OBJECT-IDENTITY
        STATUS current
        DESCRIPTION 
        "Sub-tree for Core Processes." 
        ::= { kamailioServer 4 }

-- 
-- Kamailio Server Configuration
--

    kamailioSrvCnfFullVersion OBJECT-TYPE
        SYNTAX DisplayString
        MAX-ACCESS  read-only
        STATUS current
        DESCRIPTION 
        "Full version of Kamailio"
        ::= { kamailioSrvConfig 1 }

    kamailioSrvCnfVerName OBJECT-TYPE
        SYNTAX DisplayString
        MAX-ACCESS  read-only
        STATUS current
        DESCRIPTION 
        "Version of Kamailio"
        ::= { kamailioSrvConfig 2 }

    kamailioSrvCnfVerVersion OBJECT-TYPE
        SYNTAX DisplayString
        MAX-ACCESS  read-only
        STATUS current
        DESCRIPTION 
        "Version of Kamailio"
        ::= { kamailioSrvConfig 3 }

    kamailioSrvCnfVerArch OBJECT-TYPE
        SYNTAX      DisplayString
        MAX-ACCESS  read-only
        STATUS current
        DESCRIPTION 
        "Architecture Kamailio is compiled for"
        ::= { kamailioSrvConfig 4 }

    kamailioSrvCnfVerOs	OBJECT-TYPE
        SYNTAX DisplayString
        MAX-ACCESS  read-only
        STATUS current
        DESCRIPTION 
        "Operating System Kamailio is compiled for"
        ::= { kamailioSrvConfig 5 }

    kamailioSrvCnfVerId	OBJECT-TYPE
        SYNTAX DisplayString
        MAX-ACCESS  read-only
        STATUS current
        DESCRIPTION 
        "Kamailio Version ID"
        ::= { kamailioSrvConfig 6 }

    kamailioSrvCnfVerCompTime OBJECT-TYPE
        SYNTAX DisplayString
        MAX-ACCESS  read-only
        STATUS current
        DESCRIPTION 
        "Kamailio Build time"
        ::= { kamailioSrvConfig 7 }

    kamailioSrvCnfVerCompiler OBJECT-TYPE
        SYNTAX DisplayString
        MAX-ACCESS  read-only
        STATUS current
        DESCRIPTION 
        "Kamailio Build compiler used"
        ::= { kamailioSrvConfig 8 }

    kamailioSrvCnfVerFlags OBJECT-TYPE
        SYNTAX DisplayString
        MAX-ACCESS  read-only
        STATUS current
        DESCRIPTION 
        "Kamailio Build compile time flags"
        ::= { kamailioSrvConfig 9 }


-- 
-- Kamailio Server Memory data
--
    kamailioSrvMaxMemory OBJECT-TYPE
        SYNTAX      Gauge32
        MAX-ACCESS  read-only
        STATUS current
        DESCRIPTION 
        "Maximum available Shared Memory"
        ::= { kamailioSrvMemory 1 }

    kamailioSrvFreeMemory OBJECT-TYPE
        SYNTAX      Gauge32
        MAX-ACCESS  read-only
        STATUS current
        DESCRIPTION 
        "Available free memory in the Shared Memory pool"
        ::= { kamailioSrvMemory 2 }

    kamailioSrvMaxUsed OBJECT-TYPE
        SYNTAX      Gauge32
        MAX-ACCESS  read-only
        STATUS current
        DESCRIPTION 
        "Maximum amount of memory used in the Shared Memory pool"
        ::= { kamailioSrvMemory 3 }

    kamailioSrvRealUsed OBJECT-TYPE
        SYNTAX      Gauge32
        MAX-ACCESS  read-only
        STATUS current
        DESCRIPTION 
        "Current amount of memory used in the Shared Memory pool"
        ::= { kamailioSrvMemory 4 }

    kamailioSrvMemFragments OBJECT-TYPE
        SYNTAX      Gauge32
        MAX-ACCESS  read-only
        STATUS current
        DESCRIPTION 
        "Current amount of memory fragments in the Shared Memory pool"
        ::= { kamailioSrvMemory 5 }


-- 
-- Kamailio Server Core counters
--

-- 
-- Kamailio Network Objects
--
    kamailioNetTcp OBJECT-IDENTITY
        STATUS current
        DESCRIPTION 
        "Sub-tree for TCP Network Transport objects (incl TLS conncetions)." 
        ::= { kamailioNet 1 }


    kamailioNetWebsocket OBJECT-IDENTITY
        STATUS current
        DESCRIPTION 
        "Sub-tree for Websocket Network Transport objects ." 
        ::= { kamailioNet 2 }

    kamailioNetHttp OBJECT-IDENTITY
        STATUS current
        DESCRIPTION 
        "Sub-tree for HTTP Server Transport objects ." 
        ::= { kamailioNet 3 }

    kamailioNetConfig OBJECT-IDENTITY
        STATUS current
        DESCRIPTION 
        "Sub-tree for transport properties"
        ::= { kamailioNet 4 }

--
-- TCP connection objects
--
    kamailioNetTcpTls OBJECT-IDENTITY
        STATUS current
        DESCRIPTION 
        "Sub-tree for TCP/TLS specific objects." 
        ::= { kamailioNetTcp 1 }

    kamailioNetTcpStat OBJECT-IDENTITY
        STATUS current
        DESCRIPTION 
        "Sub-tree for TCP/TLS statistics." 
        ::= { kamailioNetTcp 2 }

    kamailioNetTcpConfig OBJECT-IDENTITY
        STATUS current
        DESCRIPTION 
        "Sub-tree for TCP/TLS configuration data." 
        ::= { kamailioNetTcp 3 }

--
-- TCP connection config objects
--
    kamailioNetTcpEnabled OBJECT-TYPE
        SYNTAX  TruthValue
        MAX-ACCESS  read-only
        STATUS current
	DEFVAL { false }
        DESCRIPTION 
        "True if TCP is enabled in this server."
        ::= { kamailioNetTcpConfig 1 }

    kamailioNetTcpMaxConns OBJECT-TYPE
        SYNTAX  Integer32
        MAX-ACCESS  read-only
        STATUS current
        DESCRIPTION 
        "Maximum number of TCP connections (tcp_max_connections)"
        ::= { kamailioNetTcpConfig 2 }

    kamailioNetTcpConnTimeout OBJECT-TYPE
        SYNTAX  Integer32
        MAX-ACCESS  read-only
        STATUS current
        DESCRIPTION 
        "TCP Connection Timeout (tcp_connect_timeout)"
        ::= { kamailioNetTcpConfig 3 }

    kamailioNetTcpSendTimeout OBJECT-TYPE
        SYNTAX  Integer32
        MAX-ACCESS  read-only
        STATUS current
        DESCRIPTION 
        "Time in seconds after a TCP connection will be closed if it is not available for writing in this interval (tcp_send_timeout)"
        ::= { kamailioNetTcpConfig 4 }

    kamailioNetTcpConnLifetime OBJECT-TYPE
        SYNTAX  Integer32
        MAX-ACCESS  read-only
        STATUS current
        DESCRIPTION 
        "Lifetime in seconds for TCP sessions (tcp_connection_lifetime)"
        ::= { kamailioNetTcpConfig 5 }

    kamailioNetTcpConnLifetime OBJECT-TYPE
        SYNTAX  Integer32
        MAX-ACCESS  read-only
        STATUS current
        DESCRIPTION 
        "Maximum number of tcp connections (tcp_max_connections)"
        ::= { kamailioNetTcpConfig 6 }

    kamailioNetTcpNoConnect OBJECT-TYPE
        SYNTAX  TruthValue
        MAX-ACCESS  read-only
        STATUS current
        DESCRIPTION 
        "True if Kamailio never tries to set up outbound TCP (or TCP/TLS) connections (tcp_no_connect)"
        ::= { kamailioNetTcpConfig 7 }

    kamailioNetTcpFdCache OBJECT-TYPE
        SYNTAX  TruthValue
        MAX-ACCESS  read-only
        STATUS current
        DESCRIPTION 
        "If enabled FDs used for sending will be cached inside the process calling tcp_send (tcp_fd_cache)"
        ::= { kamailioNetTcpConfig 8 }

    kamailioNetTcpAsync OBJECT-TYPE
        SYNTAX  TruthValue
        MAX-ACCESS  read-only
        STATUS current
        DESCRIPTION 
        "True if TCP Async is enabled in this server (tcp_async)"
        ::= { kamailioNetTcpConfig 9 }

    kamailioNetTcpAsyncConnWait OBJECT-TYPE
        SYNTAX  TruthValue
        MAX-ACCESS  read-only
        STATUS current
        DESCRIPTION 
        "??? No description available "
        ::= { kamailioNetTcpConfig 10 }

    kamailioNetTcpAsyncConnWait OBJECT-TYPE
        SYNTAX  TruthValue
        MAX-ACCESS  read-only
        STATUS current
        DESCRIPTION 
        "??? No description available "
        ::= { kamailioNetTcpConfig 10 }

    kamailioNetTcpAsyncConnWqMax OBJECT-TYPE
        SYNTAX  Integer32
        MAX-ACCESS  read-only
        STATUS current
        DESCRIPTION 
        "Async TCP: Maximum bytes queued for write allowed per connection. (tcp_conn_wq_max)"
        ::= { kamailioNetTcpConfig 11 }

    kamailioNetTcpAsyncWqMax OBJECT-TYPE
        SYNTAX  Integer32
        MAX-ACCESS  read-only
        STATUS current
        DESCRIPTION 
        "Async TCP: Maximum bytes queued for write (tcp__wq_max)"
        ::= { kamailioNetTcpConfig 12 }

    kamailioNetTcpAsyncWqBlkSize OBJECT-TYPE
        SYNTAX  Integer32
        MAX-ACCESS  read-only
        STATUS current
        DESCRIPTION 
        "Async TCP: Maximum bytes queued for write (tcp_wq_blk_size)"
        ::= { kamailioNetTcpConfig 12 }

    kamailioNetTcpRdBufSize OBJECT-TYPE
        SYNTAX  Integer32
        MAX-ACCESS  read-only
        STATUS current
        DESCRIPTION 
        "Buffer size used for tcp reads (tcp_rd_buf_size)"
        ::= { kamailioNetTcpConfig 13 }

    kamailioNetTcpDeferAccept OBJECT-TYPE
        SYNTAX  TruthValue
        MAX-ACCESS  read-only
        STATUS current
        DESCRIPTION 
        "Tcp accepts will be delayed until some data is received (tcp_defer_accept)"
        ::= { kamailioNetTcpConfig 14 }

    kamailioNetTcpDelayedAck OBJECT-TYPE
        SYNTAX  TruthValue
        MAX-ACCESS  read-only
        STATUS current
        DESCRIPTION 
        "Initial ACK for opened connections will be delayed and sent with the first data segment (tcp_delayed_ack)"
        ::= { kamailioNetTcpConfig 15 }

    kamailioNetTcpSynCnt OBJECT-TYPE
        SYNTAX  TruthValue
        MAX-ACCESS  read-only
        STATUS current
        DESCRIPTION 
        "Number of SYN retransmissions before aborting a connect attempt (tcp_syncnt)"
        ::= { kamailioNetTcpConfig 16 }

    kamailioNetTcpLinger OBJECT-TYPE
        SYNTAX  Integer32
        MAX-ACCESS  read-only
        STATUS current
        DESCRIPTION 
        "Lifetime of orphaned sockets in FIN_WAIT2 state. Linux only. (tcp_linger2)"
        ::= { kamailioNetTcpConfig 17 }

    kamailioNetTcpKeepAlive OBJECT-TYPE
        SYNTAX  TruthValue
        MAX-ACCESS  read-only
        STATUS current
        DESCRIPTION 
        "True if TCP Keepalives are enabled (tcp_keepalive)"
        ::= { kamailioNetTcpConfig 18 }

    kamailioNetTcpKeepIdle OBJECT-TYPE
        SYNTAX  Integer32
        MAX-ACCESS  read-only
        STATUS current
        DESCRIPTION 
        "Time before starting to send keepalives, if the connection is idle. Linux only. (tcp_keepidle)"
        ::= { kamailioNetTcpConfig 19 }

    kamailioNetTcpKeepIntvl OBJECT-TYPE
        SYNTAX  Integer32
        MAX-ACCESS  read-only
        STATUS current
        DESCRIPTION 
        "Time interval between keepalive probes, when the previous probe failed. Linux only. (tcp_keepintvl)"
        ::= { kamailioNetTcpConfig 20 }

    kamailioNetTcpKeepCnt OBJECT-TYPE
        SYNTAX  Integer32
        MAX-ACCESS  read-only
        STATUS current
        DESCRIPTION 
        "Number of keepalives sent before dropping the connection. Linux only. (tcp_keepcnt)"
        ::= { kamailioNetTcpConfig 21 }

    kamailioNetTcpCrlfPing OBJECT-TYPE
        SYNTAX  TruthValue
        MAX-ACCESS  read-only
        STATUS current
        DESCRIPTION 
        "Enable SIP outbound TCP keep-alive using PING-PONG (CRLFCRLF - CRLF). (tcp_crlf_ping)"
        ::= { kamailioNetTcpConfig 22 }

    kamailioNetTcpAcceptAliases OBJECT-TYPE
        SYNTAX  TruthValue
        MAX-ACCESS  read-only
        STATUS current
        DESCRIPTION 
        "Reuse TCP connections based on aliases (tcp_accept_alias)"
        ::= { kamailioNetTcpConfig 23 }

    kamailioNetTcpAcceptNoCl OBJECT-TYPE
        SYNTAX  TruthValue
        MAX-ACCESS  read-only
        STATUS current
        DESCRIPTION 
        "True if Content-Length headers are required (tcp_accept_no_cl)"
        ::= { kamailioNetTcpConfig 24 }


	--- RPC settings not found. Still looking.
	---	connect_wait: 1 Depends on Async
	---	alias_flags: 1
	---	new_conn_alias_flags: 2
	---	max_tls_connections(soft): 2048

--
-- TCP connection statistic objects
--
    kamailioNetTcpConnEstablished OBJECT-TYPE
        SYNTAX      Counter32
        MAX-ACCESS  read-only
        STATUS current
        DESCRIPTION 
        "Incremented each time a TCP connection is established."
        ::= { kamailioNetTcpStat 1 }

    kamailioNetTcpConnFailed OBJECT-TYPE
        SYNTAX      Counter32
        MAX-ACCESS  read-only
        STATUS current
        DESCRIPTION 
        "Number of failed active TCP connection attempts."
        ::= { kamailioNetTcpStat 2 }

    kamailioNetTcpConnReset OBJECT-TYPE
        SYNTAX      Counter32
        MAX-ACCESS  read-only
        STATUS current
        DESCRIPTION 
        "Number of reset TCP connections"
        ::= { kamailioNetTcpStat 3 }

    kamailioNetTcpConnSuccess OBJECT-TYPE
        SYNTAX      Counter32
        MAX-ACCESS  read-only
        STATUS current
        DESCRIPTION 
        "Number of successful TCP connections"
        ::= { kamailioNetTcpStat 4 }

    kamailioNetTcpConnOpen OBJECT-TYPE
        SYNTAX      Gauge32
        MAX-ACCESS  read-only
        STATUS current
        DESCRIPTION 
        "Number of current open TCP connections"
        ::= { kamailioNetTcpStat 5 }

    kamailioNetTcpConnPassiveOpen OBJECT-TYPE
        SYNTAX      Counter32
        MAX-ACCESS  read-only
        STATUS current
        DESCRIPTION 
        "Total number of accepted TCP connections (so far)."
        ::= { kamailioNetTcpStat 6 }

    kamailioNetTcpConnSuccess OBJECT-TYPE
        SYNTAX      Counter32
        MAX-ACCESS  read-only
        STATUS current
        DESCRIPTION 
        "Total number of successfully active opened TCP connections"
        ::= { kamailioNetTcpStat 7 }

    kamailioNetTcpConnReject OBJECT-TYPE
        SYNTAX      Counter32
        MAX-ACCESS  read-only
        STATUS current
        DESCRIPTION 
        "Number of rejected incoming TCP connections."
        ::= { kamailioNetTcpStat 8 }

--
-- Kamailio Network Configuration
--
    kamailioNetConfUdpTransport OBJECT-TYPE
        SYNTAX  TruthValue
        MAX-ACCESS  read-only
        STATUS current
	DEFVAL { false }
        DESCRIPTION 
        "True if UDP is active in this server."
        ::= { kamailioNetConfig 1 }

    kamailioNetConfUdpDtlsTransport OBJECT-TYPE
        SYNTAX  TruthValue
        MAX-ACCESS  read-only
        STATUS current
	DEFVAL { false }
        DESCRIPTION 
        "True if UDP/DTLS is active in this server. (Future reservation)"
        ::= { kamailioNetConfig 2 }

    kamailioNetConfTcpTransport OBJECT-TYPE
        SYNTAX  TruthValue
        MAX-ACCESS  read-only
        STATUS current
	DEFVAL { false }
        DESCRIPTION 
        "True if TCP is active in this server."
        ::= { kamailioNetConfig 3 }

    kamailioNetConfTcpTlsTransport OBJECT-TYPE
        SYNTAX  TruthValue
        MAX-ACCESS  read-only
        STATUS current
	DEFVAL { false }
        DESCRIPTION 
        "True if TCP/TLS is active in this server."
        ::= { kamailioNetConfig 4 }

    kamailioNetConfSctpTransport OBJECT-TYPE
        SYNTAX  TruthValue
        MAX-ACCESS  read-only
        STATUS current
	DEFVAL { false }
        DESCRIPTION 
        "True if Sctp is enabled in this server."
        ::= { kamailioNetConfig 5 }

    kamailioNetConfSctpTlsTransport OBJECT-TYPE
        SYNTAX  TruthValue
        MAX-ACCESS  read-only
        STATUS current
	DEFVAL { false }
        DESCRIPTION 
        "True if Sctp/TLS is enabled in this server. (Future reservation)"
        ::= { kamailioNetConfig 6 }

    kamailioNetConfWsTransport OBJECT-TYPE
        SYNTAX  TruthValue
        MAX-ACCESS  read-only
        STATUS current
	DEFVAL { false }
        DESCRIPTION 
        "True if WS - WebSocket Transport- is enabled in this server."
        ::= { kamailioNetConfig 7 }

    kamailioNetConfWsTlsTransport OBJECT-TYPE
        SYNTAX  TruthValue
        MAX-ACCESS  read-only
        STATUS current
	DEFVAL { false }
        DESCRIPTION 
        "True if WSS - WebSocket Transport with TLS- is enabled in this server."
        ::= { kamailioNetConfig 8 }

    kamailioNetConfHttpServer OBJECT-TYPE
        SYNTAX  TruthValue
        MAX-ACCESS  read-only
        STATUS current
	DEFVAL { false }
        DESCRIPTION 
        "True if the embedded HTTP server (xhttp module) is loaded in this server."
        ::= { kamailioNetConfig 9 }

    kamailioNetConfMsrpRelay OBJECT-TYPE
        SYNTAX  TruthValue
        MAX-ACCESS  read-only
        STATUS current
	DEFVAL { false }
        DESCRIPTION 
        "True if the MSRP Relay server is loaded in this server."
        ::= { kamailioNetConfig 10 }

    kamailioNetConfStunServer OBJECT-TYPE
        SYNTAX  TruthValue
        MAX-ACCESS  read-only
        STATUS current
	DEFVAL { false }
        DESCRIPTION 
        "True if the STUN Server server (SIP Outbound) is loaded in this server."
        ::= { kamailioNetConfig 11 }

--
-- Websocket Connection Objects
--
    kamailioNetWsStat OBJECT-IDENTITY
        STATUS current
        DESCRIPTION 
        "Sub-tree for Websocket statistics." 
        ::= { kamailioNetWebsocket 1 }

   kamailioNetWsConfig OBJECT-IDENTITY
        STATUS current
        DESCRIPTION 
        "Sub-tree for Websocket configuration objects." 
        ::= { kamailioNetWebsocket 2 }

--
-- Kamailio WebSocket Configuration  Objects
--
	--- Currently empty.

--
-- Kamailio WebSocket Statistics  Objects
--

    kamailioNetWsConnsActive OBJECT-TYPE
        SYNTAX      Gauge
        MAX-ACCESS  read-only
        STATUS current
        DESCRIPTION 
        "Number of currently active websocket connections"
        ::= { kamailioNetWsStat 1 }

    kamailioNetWsConnsActiveMax OBJECT-TYPE
        SYNTAX      Gauge
        MAX-ACCESS  read-only
        STATUS current
        DESCRIPTION 
        "The maximum number of active websocket connections since process start"
        ::= { kamailioNetWsStat 2 }

    kamailioNetWsConnsFailed OBJECT-TYPE
        SYNTAX      Counter32
        MAX-ACCESS  read-only
        STATUS current
        DESCRIPTION 
        "The number of failed websocket connections since process start"
        ::= { kamailioNetWsStat 3 }

    kamailioNetWsConnsClosedLocal OBJECT-TYPE
        SYNTAX      Counter32
        MAX-ACCESS  read-only
        STATUS current
        DESCRIPTION 
        "The number of locally closed websocket connections"
        ::= { kamailioNetWsStat 4 }

    kamailioNetWsConnsClosedRemote OBJECT-TYPE
        SYNTAX      Counter32
        MAX-ACCESS  read-only
        STATUS current
        DESCRIPTION 
        "The number of closed websocket connections by remote peer"
        ::= { kamailioNetWsStat 5 }

    kamailioNetWsFramesRx OBJECT-TYPE
        SYNTAX      Counter32
        MAX-ACCESS  read-only
        STATUS current
        DESCRIPTION 
        "The number of received websocket frames"
        ::= { kamailioNetWsStat 6 }

    kamailioNetWsFramesTx OBJECT-TYPE
        SYNTAX      Counter32
        MAX-ACCESS  read-only
        STATUS current
        DESCRIPTION 
        "The number of transmitted websocket frames"
        ::= { kamailioNetWsStat 7 }

    kamailioNetWsHandshakeSuccess OBJECT-TYPE
        SYNTAX      Counter32
        MAX-ACCESS  read-only
        STATUS current
        DESCRIPTION 
        "The number of transmitted websocket frames"
        ::= { kamailioNetWsStat 8 }

    kamailioNetWsHandshakeFailed OBJECT-TYPE
        SYNTAX      Counter32
        MAX-ACCESS  read-only
        STATUS current
        DESCRIPTION 
        "The number of transmitted websocket frames"
        ::= { kamailioNetWsStat 9 }


--
-- Kamailio Message Objects
--

--
-- Message Statistics 
--
    kamailioMsgStats OBJECT-IDENTITY
        STATUS current
        DESCRIPTION 
        "Sub-tree for Message Statistics." 
        ::= { kamailioMsgs 3 }

    kamailioMsgQueueDepth       OBJECT-TYPE
        SYNTAX      Gauge32
        MAX-ACCESS  read-only
        STATUS      current
        DESCRIPTION
            "The number of packets (udp or tcp) waiting in the OS network queue, 
             waiting to be processed."
        ::= { kamailioMsgStats 1 }

    kamailioMsgQueueMinorThreshold    OBJECT-TYPE
        SYNTAX      Integer32
        MAX-ACCESS  read-only
        STATUS      current
        DESCRIPTION
            "When the kamailioMsgQueueDepth reaches this point, a minor alarm 
             will be generated. This value reflects the configured value; if it
             is set to -1, then the alarm is never sent."
        ::= { kamailioMsgStats 2 }
        
    kamailioMsgQueueMajorThreshold    OBJECT-TYPE
        SYNTAX      Integer32
        MAX-ACCESS  read-only
        STATUS      current
        DESCRIPTION
            "When the kamailioMsgQueueDepth reaches this point, a major alarm 
             will be generated. This value reflects the configured value; if it
             is set to -1, then the alarm is never sent."
        ::= { kamailioMsgStats 3 }
--
-- Message Alarms
--
    kamailioMsgAlarms OBJECT-IDENTITY
        STATUS current
        DESCRIPTION 
        "Sub-tree for Message Alarms."
        ::= { kamailioMsgs 4 }

    kamailioMsgQueueDepthAlarmStatus   OBJECT-TYPE
        SYNTAX      X731AlarmStatus
        MAX-ACCESS  read-only
        STATUS      current
        DESCRIPTION
            "This status variable reports the alarm levels that have been
             generated for the message queue depth.
               
             The thresholds are defined in the Kamailio configuration; if they 
             are not configured, this alarm status will always be clear. 
             Specifically, in this case no bits will be toggled, and therefore
             this scalar will return 00.
             
             This scalar follows the X731AlarmStatus specs, and can take on
             the following values:
             
             underRepair(0), critical(1), major(2), minor(3), 
             alarmOutstanding(4), unknown(5)"
        ::= { kamailioMsgAlarms 1 }

    kamailioMsgQueueDepthMinorAlarm  OBJECT-TYPE
        SYNTAX      X731AlarmState
        MAX-ACCESS  read-only
        STATUS      current
        DESCRIPTION
            "This variable indicates whether the minor message queue depth 
             threshold has been surpassed.
                clear(0) the queue depth is below the configured threshold.
                minor(1) the queue depth has exceeded the configured threshold."
        ::= { kamailioMsgAlarms 2 }
    
    kamailioMsgQueueDepthMajorAlarm  OBJECT-TYPE
        SYNTAX      X731AlarmState
        MAX-ACCESS  read-only
        STATUS      current
        DESCRIPTION
            "This variable indicates whether the major message queue depth 
             threshold has been surpassed.               
                clear(0) the queue depth is below the configured threshold.
                major(2) the queue depth has exceeded the configured threshold."
        ::= { kamailioMsgAlarms 3 }
--
-- Kamailio Dialog Objects
--

--
-- The Dialog Table: 
--    contains information about currently active calls.
--

    kamailioDialogTable   OBJECT-TYPE
          SYNTAX      SEQUENCE OF  KamailioDialogTableEntry
          MAX-ACCESS  not-accessible
          STATUS      current
          DESCRIPTION
              "This table contains information on all active calls in
               the system."
          ::= { kamailioDialog 1 }
  
    kamailioDialogTableEntry   OBJECT-TYPE
          SYNTAX      KamailioDialogTableEntry
          MAX-ACCESS  not-accessible
          STATUS      current
          DESCRIPTION
             "This entry contains information for a single active call in the
              system."
          INDEX { kamailioDialogIndex }
          ::= { kamailioDialogTable 1 }

    KamailioDialogTableEntry ::= 
        SEQUENCE {
            kamailioDialogIndex              Unsigned32,
            kamailioDialogType               INTEGER,
            kamailioDialogToUri              SnmpAdminString,
            kamailioDialogFromUri            SnmpAdminString,
            kamailioDialogState              INTEGER,
            kamailioDialogStartTime          DateAndTime,
            kamailioDialogLastUpdateTime     DateAndTime,
            kamailioDialogExpiryTime         DateAndTime
        }

    kamailioDialogIndex OBJECT-TYPE
        SYNTAX      Unsigned32
        MAX-ACCESS  not-accessible
        STATUS current
        DESCRIPTION 
        "The index of this dialog."
        ::= { kamailioDialogTableEntry 1 }

   kamailioDialogType OBJECT-TYPE
        SYNTAX      INTEGER {
            invite(1),
            subscribe(2)
        }
        MAX-ACCESS  read-only
        STATUS current
        DESCRIPTION 
        "The type of Dialog:
            invite(1)     - the dialog was created with a SIP INVITE.
            subscribe(2)  - the dialog was created with a SIP SUBSCRIBE."
        ::= { kamailioDialogTableEntry 2 }
                
    kamailioDialogToUri OBJECT-TYPE
        SYNTAX      SnmpAdminString
        MAX-ACCESS  read-only
        STATUS current
        DESCRIPTION 
        "The URI of the To header."
        ::= { kamailioDialogTableEntry 3 }
        
    kamailioDialogFromUri OBJECT-TYPE
        SYNTAX      SnmpAdminString
        MAX-ACCESS  read-only
        STATUS current
        DESCRIPTION 
        "The URI of the From header."
        ::= { kamailioDialogTableEntry 4 }
        
    kamailioDialogState OBJECT-TYPE
        SYNTAX  INTEGER {
            unconfirmed(0),
            early(1),
            confirmed(2),
            terminalted(3)
        }
        MAX-ACCESS read-only
        STATUS current
        DESCRIPTION
        "The Dialogue state:
            unconfirmed (0)  - we do not yet have a dialog, but a request has
                               been made and we may create one in the future. 
                               All calls begin in this state.
            early (1)        - dialog migrates to this state when we receive a 
                               101-199 response.
            confirmed (2)    - dialog migrates from unconfirmed OR early to this 
                               state when we received a 200-299 response.
            terminated (3)   - dialog migrates from unconfirmed OR early to this 
                               state when a final 3xx-4xx-5xx-6xx is message is
                               received.
              
          terminated dialogs stay present in the system for only a short period 
          of time, and then are cleared by Kamailio."
        ::= { kamailioDialogTableEntry 5 }
        
    kamailioDialogStartTime OBJECT-TYPE
        SYNTAX      DateAndTime
        MAX-ACCESS  read-only
        STATUS current
        DESCRIPTION 
        "The time this dialog was started."
        ::= { kamailioDialogTableEntry 6 }
        
    kamailioDialogLastUpdateTime OBJECT-TYPE
        SYNTAX      DateAndTime
        MAX-ACCESS  read-only
        STATUS current
        DESCRIPTION 
        "The last time this dialog was updated; ie, when the last SIP
         message for this dialog was seen."
        ::= { kamailioDialogTableEntry 7 }        

    kamailioDialogExpiryTime OBJECT-TYPE
        SYNTAX      DateAndTime
        MAX-ACCESS  read-only
        STATUS current
        DESCRIPTION 
        "The time at which this dialog will automatically expire."
        ::= { kamailioDialogTableEntry 8 }        


    kamailioDialogStats OBJECT-IDENTITY
        STATUS current
        DESCRIPTION 
        "Sub-section for Dialog counters and statistics."
        ::= { kamailioDialog 2 }

    kamailioCurNumDialogs     OBJECT-TYPE
        SYNTAX      Gauge32
        MAX-ACCESS  read-only
        STATUS      current
        DESCRIPTION
            "The current number of dialogs either in EARLY or CONFIRMED 
             state."
        ::= { kamailioDialogStats 1 }
        
    kamailioCurNumDialogsInProgress     OBJECT-TYPE
        SYNTAX      Gauge32
        MAX-ACCESS  read-only
        STATUS      current
        DESCRIPTION
            "The current number of CONFIRMED dialogs."
        ::= { kamailioDialogStats 2 }
        
    kamailioCurNumDialogsInSetup     OBJECT-TYPE
        SYNTAX      Gauge32
        MAX-ACCESS  read-only
        STATUS      current
        DESCRIPTION
            "The current number of EARLY dialogs."
        ::= { kamailioDialogStats 3 }
        
    kamailioTotalNumFailedDialogSetups     OBJECT-TYPE
        SYNTAX      Counter32
        MAX-ACCESS  read-only
        STATUS      current
        DESCRIPTION
            "The total number of calls that failed with an error. 
             The following codes define a failed call:"
        ::= { kamailioDialogStats 4 }

    kamailioDialogLimitMinorThreshold    OBJECT-TYPE
        SYNTAX      Integer32
        MAX-ACCESS  read-only
        STATUS      current
        DESCRIPTION
            "The configured minor threshold indicating the kamailio system has 
             reached a high level of dialogs. -1 indicates the value
             is not configured, and the alarm will never be set."
        ::= { kamailioDialogStats 5 }

    kamailioDialogLimitMajorThreshold    OBJECT-TYPE
        SYNTAX      Integer32
        MAX-ACCESS  read-only
        STATUS      current
        DESCRIPTION
            "The configured threshold indicating the kamailio system has reached
             a maximum number of dialogs, and perhaps performace will suffer.
             -1 indicates the value is not configured, and alarms will never be 
             set, and the usage state will never be reported as 'busy'."
        ::= { kamailioDialogStats 6 }

    kamailioTotalNumDialogSetups     OBJECT-TYPE
        SYNTAX      Counter32
        MAX-ACCESS  read-only
        STATUS      current
        DESCRIPTION
            "The total number of calls (answered and failed)."
        ::= { kamailioDialogStats 7 }


--
-- Dialog State
--

    kamailioDialogStates  OBJECT-IDENTITY
        STATUS current
        DESCRIPTION
        "a sub-tree for Kamailio's dialog tracking states."
        ::= { kamailioDialog 3 }
    
    kamailioDialogUsageState     OBJECT-TYPE
        SYNTAX      X731UsageState
        MAX-ACCESS  read-only
        STATUS      current
        DESCRIPTION
        "The current usage state of Kamailio's dialog tracking:
            idle(0)   - no dialogs are currently being tracked.
            active(1) - at least 1 dialog is being tracked.
            busy(2)   - the maximum number of dialogs are being tracked.
                        
         The 'busy' point is based on a configuration variable (the same as
         kamailioDialogMajorLimitThreshold): if this value is -1, then the server
         is never considered 'busy'."
    ::= { kamailioDialogStates 1 }

--
-- Dialog Alarms
--
    kamailioDialogAlarms   OBJECT-IDENTITY
        STATUS current
        DESCRIPTION 
        "Sub-tree for call alarms." 
    ::= { kamailioDialog 4 }

    kamailioDialogLimitAlarmStatus  OBJECT-TYPE
        SYNTAX      X731AlarmStatus
        MAX-ACCESS  read-only
        STATUS      current
        DESCRIPTION
           "This alarm status reports the overall alarm status of the dialog
            sub-system. If the thresholds are not configured, then this status
            will always be 'clear'.

            This scalar follows the X731AlarmStatus specs, and can take on
            the following values:
             
            underRepair(0), critical(1), major(2), minor(3), 
            alarmOutstanding(4), unknown(5)"
        ::= { kamailioDialogAlarms 1 }

   kamailioDialogLimitMinorAlarm  OBJECT-TYPE
        SYNTAX      X731AlarmState
        MAX-ACCESS  read-only
        STATUS      current
        DESCRIPTION
           "The Kamailio system is approaching or has reached its configured 
            minor dialog limit threshold.
                clear(0) - the current number of dialogs is below the configured
                           threshold.
                minor(1) - the current number of dialogs has reached or exceeded
                           the configured threshold.
                           
            The threshold is defined in the Kamailio configuration; if it 
             is not configured, this alarm will not be sent."
        ::= { kamailioDialogAlarms 2 }

   kamailioDialogLimitMajorAlarm  OBJECT-TYPE
        SYNTAX      X731AlarmState
        MAX-ACCESS  read-only
        STATUS      current
        DESCRIPTION
           "The Kamailio system is approaching or has reached its configured 
            dialog limit.
                clear(0) - the current number of dialogs is below the configured
                           threshold.
                major(2) - the current number of dialogs has reached or exceeded
                           the configured threshold.
            
            The threshold is defined in the Kamailio configuration; if it 
             is not configured, this alarm will not be sent."
        ::= { kamailioDialogAlarms 3 }

-- 
-- Notifications
--

--
-- This section defines the SNMP traps, or notifications, that the KAMAILIO-MIB
-- supports.
--

    kamailioMIBNotifications  OBJECT-IDENTITY
        STATUS current
        DESCRIPTION 
        "A sub-section for reverse-mapping between SNMPv1 and SNMPv2 events."
        ::= { kamailioMIBEvents 0 } 
        
    kamailioMsgQueueDepthMinorEvent NOTIFICATION-TYPE
        OBJECTS {
          kamailioMsgQueueDepth, kamailioMsgQueueMinorThreshold
        }
        STATUS  current
        DESCRIPTION
        "The message queue depth (as reported by kamailioMsgQueueDepth) has 
         exceeded the minor configured threshold kamailioMsgQueueMinorThreshold."
        ::= { kamailioMIBNotifications 1 }
        
    kamailioMsgQueueDepthMajorEvent NOTIFICATION-TYPE
        OBJECTS {
            kamailioMsgQueueDepth, kamailioMsgQueueMajorThreshold
        }
        STATUS  current
        DESCRIPTION
        "The message queue depth (as reported by kamailioMsgQueueDepth) has 
         exceeded the minor configured threshold kamailioMsgQueueMinorThreshold."
        ::= { kamailioMIBNotifications 2 }
        
    kamailioDialogLimitMinorEvent NOTIFICATION-TYPE
        OBJECTS {
            kamailioCurNumDialogs, kamailioDialogLimitMinorThreshold
        }
        STATUS  current
        DESCRIPTION
        "The number of dialogs being tracked in the system (as reported by
         kamailioCurNumDialogs) has exceeded the minor configured threshold 
         kamailioDialogLimitMinorThreshold."
        ::= { kamailioMIBNotifications 3 }

    kamailioDialogLimitMajorEvent NOTIFICATION-TYPE
        OBJECTS {
            kamailioCurNumDialogs, kamailioDialogLimitMajorThreshold
        }
        STATUS  current
        DESCRIPTION
        "The number of dialogs being tracked in the system (as reported by
         kamailioCurNumDialogs) has exceeded the major configured threshold 
         kamailioDialogLimitMajorThreshold."
        ::= { kamailioMIBNotifications 4 }


--
-- Conformance
--

--
-- Compliance Statements
--
    kamailioCompliance   MODULE-COMPLIANCE
        STATUS      current
        DESCRIPTION
            "The compliance statement for Kamailio in the SOMAvoice product."

        MODULE -- this module
            MANDATORY-GROUPS { kamailioX731Group,
                               kamailioStatsGroup,
                               kamailioAlarmsGroup,
                               kamailioMsgQueueEvents,
                               kamailioDialogLimitEvents }
        ::= { kamailioConform 1 }

    kamailioGroups  OBJECT-IDENTITY
        STATUS current
        DESCRIPTION 
        "Sub-tree for defining the conformance groups."
        ::= { kamailioConform 2 }
        
    kamailioNotifications OBJECT-IDENTITY
        STATUS current
        DESCRIPTION
        "Sub-tree for defining the conformance notifications."
        ::= { kamailioConform 3 }

--
-- Units of Conformance
--
    kamailioX731Group    OBJECT-GROUP
        OBJECTS {
            kamailioDialogUsageState
        }
        STATUS  current
        DESCRIPTION
            "A collection of objects providing X.731 state and alarm status
             information in Kamailio."
        ::= { kamailioGroups 1 }

    kamailioStatsGroup   OBJECT-GROUP
        OBJECTS {
            kamailioMsgQueueDepth,
            kamailioMsgQueueMinorThreshold,
            kamailioMsgQueueMajorThreshold,
            kamailioDialogType,
            kamailioDialogToUri,
            kamailioDialogFromUri,
            kamailioDialogState,
            kamailioDialogStartTime,
            kamailioDialogLastUpdateTime,
            kamailioDialogExpiryTime,
            kamailioCurNumDialogs,
            kamailioCurNumDialogsInProgress,
            kamailioCurNumDialogsInSetup,
            kamailioTotalNumFailedDialogSetups,
            kamailioDialogLimitMinorThreshold,
            kamailioDialogLimitMajorThreshold,
            kamailioTotalNumDialogSetups
        }
        STATUS  current
        DESCRIPTION
            "A collection of objects providing statistics in Kamailio."
        ::= { kamailioGroups 2 }

    kamailioAlarmsGroup   OBJECT-GROUP
        OBJECTS {
            kamailioMsgQueueDepthAlarmStatus,
            kamailioMsgQueueDepthMinorAlarm,
            kamailioMsgQueueDepthMajorAlarm,
            kamailioDialogLimitAlarmStatus,
            kamailioDialogLimitMinorAlarm,
            kamailioDialogLimitMajorAlarm
        }
        STATUS  current
        DESCRIPTION
            "A collection of objects providing stateful alarm information in
             Kamailio."
        ::= { kamailioGroups 3 }
    
    kamailioMsgQueueEvents   NOTIFICATION-GROUP
        NOTIFICATIONS {
            kamailioMsgQueueDepthMinorEvent,
            kamailioMsgQueueDepthMajorEvent
        }
        STATUS current
        DESCRIPTION
            "A collection of events for the message queue depth."
        ::= { kamailioNotifications 1 }

    kamailioDialogLimitEvents   NOTIFICATION-GROUP
        NOTIFICATIONS {
            kamailioDialogLimitMinorEvent,
            kamailioDialogLimitMajorEvent
        }
        STATUS current
        DESCRIPTION
            "A collection of events for dialog tracking."
        ::= { kamailioNotifications 2 }

END

-- vim:ts=4:et:sw=4:si:ai:tw=78
