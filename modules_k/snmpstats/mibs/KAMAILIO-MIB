-- ***********************************************************************
-- KAMAILIO-MIB:  KAMAILIO MIB
--
-- Date of Creation: Januay 2006
--
-- This MIB provides information related to the Kamailio SIP Router.
-- 
-- Copyright (c) The Internet Society (2006)
-- Ammendments (c) Soma Networks, Inc. (2006)
--
-- All rights reserved.
-- *****************************************************************

KAMAILIO-MIB DEFINITIONS ::= BEGIN

    IMPORTS
        MODULE-IDENTITY,
        OBJECT-TYPE, 
        OBJECT-IDENTITY,
        NOTIFICATION-TYPE,
        Integer32,
        Unsigned32,
        Counter32,
        Counter64,
        Gauge32
            FROM SNMPv2-SMI
            
        DateAndTime
            FROM SNMPv2-TC

        SnmpAdminString
            FROM SNMP-FRAMEWORK-MIB

        X731UsageState,
        X731AlarmStatus,
        X731AlarmState
            FROM KAMAILIO-TC
            
        MODULE-COMPLIANCE,
        OBJECT-GROUP,
        NOTIFICATION-GROUP
            FROM SNMPv2-CONF

        kamailioModules, kamailioMIB
            FROM KAMAILIO-REG-MIB;

    kamailioModule MODULE-IDENTITY
        LAST-UPDATED "201301081200Z"
        ORGANIZATION "Kamailio"
        CONTACT-INFO 
            "http://www.kamailio.org"
        DESCRIPTION
            "Kamailio MIB module.
             This module defines objects which are neceesary to monitor an
             instance of Kamailio.
             
             The objects in this MIB are intended to be used in conjunction
             with those rovided in KAMAILIO-SIP-COMMON-MIB and
             KAMAILIO-SIP-SERVER-MIB.  In particular, this MIB defines the X.731
             attributes required to monitor the Kamailio subsystems and the
             Kamailio core itself."
        REVISION   "200605021200Z"
        DESCRIPTION
            "clarified some of the statisitcs collected, added the alarm 
            states and notifications."
        REVISION   "200603231200Z"
        DESCRIPTION
           "changed ownership to Kamailio group, and made it SMIv2 compliant."
        REVISION   "200601061200Z"
        DESCRIPTION
           "Initial version of the KAMAILIO-MIB module."
        REVISION   "201301081200Z"
        DESCRIPTION
           "Renamed MIB and mib entries to new product name, Kamailio."
        ::= { kamailioModules 5 }

--
-- Top-Level Components of this MIB.
--
    kamailioObjects OBJECT-IDENTITY
        STATUS current
        DESCRIPTION 
        "Sub-tree for accessible objects in the MIB."
        ::= { kamailioMIB 1 } 

    kamailioMIBEvents OBJECT-IDENTITY
        STATUS current
        DESCRIPTION
        "A sub-tree for all the KAMAILIO-MIB related events and traps."
        ::= {kamailioMIB 2 }

    kamailioConform OBJECT-IDENTITY
        STATUS current
        DESCRIPTION 
        "Sub-tree for Conformance specifications."
        ::= { kamailioMIB 3 }
                                

--
-- kamailioObjects sub-components
--
    kamailioServer  OBJECT-IDENTITY
        STATUS current
        DESCRIPTION 
        "Sub-tree for Server state, alarms, and management."
        ::= { kamailioObjects 1 }

    kamailioMsgs  OBJECT-IDENTITY
        STATUS current
        DESCRIPTION 
        "Sub-tree for tracking of individual SIP messages processed by Kamailio."
        ::= { kamailioObjects 2 }

   kamailioDialog  OBJECT-IDENTITY
        STATUS current
        DESCRIPTION 
        "Sub-tree for tracking of SIP Dialogs being processed by Kamailio."
    ::= { kamailioObjects 3 }

-- 
-- Kamailio Server Objects
--


--
-- Kamailio Message Objects
--

--
-- Message Statistics 
--
    kamailioMsgStats OBJECT-IDENTITY
        STATUS current
        DESCRIPTION 
        "Sub-tree for Message Statistics." 
        ::= { kamailioMsgs 3 }

    kamailioMsgQueueDepth       OBJECT-TYPE
        SYNTAX      Gauge32
        MAX-ACCESS  read-only
        STATUS      current
        DESCRIPTION
            "The number of packets (udp or tcp) waiting in the OS network queue, 
             waiting to be processed."
        ::= { kamailioMsgStats 1 }

    kamailioMsgQueueMinorThreshold    OBJECT-TYPE
        SYNTAX      Integer32
        MAX-ACCESS  read-only
        STATUS      current
        DESCRIPTION
            "When the kamailioMsgQueueDepth reaches this point, a minor alarm 
             will be generated. This value reflects the configured value; if it
             is set to -1, then the alarm is never sent."
        ::= { kamailioMsgStats 2 }
        
    kamailioMsgQueueMajorThreshold    OBJECT-TYPE
        SYNTAX      Integer32
        MAX-ACCESS  read-only
        STATUS      current
        DESCRIPTION
            "When the kamailioMsgQueueDepth reaches this point, a major alarm 
             will be generated. This value reflects the configured value; if it
             is set to -1, then the alarm is never sent."
        ::= { kamailioMsgStats 3 }
--
-- Message Alarms
--
    kamailioMsgAlarms OBJECT-IDENTITY
        STATUS current
        DESCRIPTION 
        "Sub-tree for Message Alarms."
        ::= { kamailioMsgs 4 }

    kamailioMsgQueueDepthAlarmStatus   OBJECT-TYPE
        SYNTAX      X731AlarmStatus
        MAX-ACCESS  read-only
        STATUS      current
        DESCRIPTION
            "This status variable reports the alarm levels that have been
             generated for the message queue depth.
               
             The thresholds are defined in the Kamailio configuration; if they 
             are not configured, this alarm status will always be clear. 
             Specifically, in this case no bits will be toggled, and therefore
             this scalar will return 00.
             
             This scalar follows the X731AlarmStatus specs, and can take on
             the following values:
             
             underRepair(0), critical(1), major(2), minor(3), 
             alarmOutstanding(4), unknown(5)"
        ::= { kamailioMsgAlarms 1 }

    kamailioMsgQueueDepthMinorAlarm  OBJECT-TYPE
        SYNTAX      X731AlarmState
        MAX-ACCESS  read-only
        STATUS      current
        DESCRIPTION
            "This variable indicates whether the minor message queue depth 
             threshold has been surpassed.
                clear(0) the queue depth is below the configured threshold.
                minor(1) the queue depth has exceeded the configured threshold."
        ::= { kamailioMsgAlarms 2 }
    
    kamailioMsgQueueDepthMajorAlarm  OBJECT-TYPE
        SYNTAX      X731AlarmState
        MAX-ACCESS  read-only
        STATUS      current
        DESCRIPTION
            "This variable indicates whether the major message queue depth 
             threshold has been surpassed.               
                clear(0) the queue depth is below the configured threshold.
                major(2) the queue depth has exceeded the configured threshold."
        ::= { kamailioMsgAlarms 3 }
--
-- Kamailio Dialog Objects
--

--
-- The Dialog Table: 
--    contains information about currently active calls.
--

    kamailioDialogTable   OBJECT-TYPE
          SYNTAX      SEQUENCE OF  KamailioDialogTableEntry
          MAX-ACCESS  not-accessible
          STATUS      current
          DESCRIPTION
              "This table contains information on all active calls in
               the system."
          ::= { kamailioDialog 1 }
  
    kamailioDialogTableEntry   OBJECT-TYPE
          SYNTAX      KamailioDialogTableEntry
          MAX-ACCESS  not-accessible
          STATUS      current
          DESCRIPTION
             "This entry contains information for a single active call in the
              system."
          INDEX { kamailioDialogIndex }
          ::= { kamailioDialogTable 1 }

    KamailioDialogTableEntry ::= 
        SEQUENCE {
            kamailioDialogIndex              Unsigned32,
            kamailioDialogType               INTEGER,
            kamailioDialogToUri              SnmpAdminString,
            kamailioDialogFromUri            SnmpAdminString,
            kamailioDialogState              INTEGER,
            kamailioDialogStartTime          DateAndTime,
            kamailioDialogLastUpdateTime     DateAndTime,
            kamailioDialogExpiryTime         DateAndTime
        }

    kamailioDialogIndex OBJECT-TYPE
        SYNTAX      Unsigned32
        MAX-ACCESS  not-accessible
        STATUS current
        DESCRIPTION 
        "The index of this dialog."
        ::= { kamailioDialogTableEntry 1 }

   kamailioDialogType OBJECT-TYPE
        SYNTAX      INTEGER {
            invite(1),
            subscribe(2)
        }
        MAX-ACCESS  read-only
        STATUS current
        DESCRIPTION 
        "The type of Dialog:
            invite(1)     - the dialog was created with a SIP INVITE.
            subscribe(2)  - the dialog was created with a SIP SUBSCRIBE."
        ::= { kamailioDialogTableEntry 2 }
                
    kamailioDialogToUri OBJECT-TYPE
        SYNTAX      SnmpAdminString
        MAX-ACCESS  read-only
        STATUS current
        DESCRIPTION 
        "The URI of the To header."
        ::= { kamailioDialogTableEntry 3 }
        
    kamailioDialogFromUri OBJECT-TYPE
        SYNTAX      SnmpAdminString
        MAX-ACCESS  read-only
        STATUS current
        DESCRIPTION 
        "The URI of the From header."
        ::= { kamailioDialogTableEntry 4 }
        
    kamailioDialogState OBJECT-TYPE
        SYNTAX  INTEGER {
            unconfirmed(0),
            early(1),
            confirmed(2),
            terminalted(3)
        }
        MAX-ACCESS read-only
        STATUS current
        DESCRIPTION
        "The Dialogue state:
            unconfirmed (0)  - we do not yet have a dialog, but a request has
                               been made and we may create one in the future. 
                               All calls begin in this state.
            early (1)        - dialog migrates to this state when we receive a 
                               101-199 response.
            confirmed (2)    - dialog migrates from unconfirmed OR early to this 
                               state when we received a 200-299 response.
            terminated (3)   - dialog migrates from unconfirmed OR early to this 
                               state when a final 3xx-4xx-5xx-6xx is message is
                               received.
              
          terminated dialogs stay present in the system for only a short period 
          of time, and then are cleared by Kamailio."
        ::= { kamailioDialogTableEntry 5 }
        
    kamailioDialogStartTime OBJECT-TYPE
        SYNTAX      DateAndTime
        MAX-ACCESS  read-only
        STATUS current
        DESCRIPTION 
        "The time this dialog was started."
        ::= { kamailioDialogTableEntry 6 }
        
    kamailioDialogLastUpdateTime OBJECT-TYPE
        SYNTAX      DateAndTime
        MAX-ACCESS  read-only
        STATUS current
        DESCRIPTION 
        "The last time this dialog was updated; ie, when the last SIP
         message for this dialog was seen."
        ::= { kamailioDialogTableEntry 7 }        

    kamailioDialogExpiryTime OBJECT-TYPE
        SYNTAX      DateAndTime
        MAX-ACCESS  read-only
        STATUS current
        DESCRIPTION 
        "The time at which this dialog will automatically expire."
        ::= { kamailioDialogTableEntry 8 }        


    kamailioDialogStats OBJECT-IDENTITY
        STATUS current
        DESCRIPTION 
        "Sub-section for Dialog counters and statistics."
        ::= { kamailioDialog 2 }

    kamailioCurNumDialogs     OBJECT-TYPE
        SYNTAX      Gauge32
        MAX-ACCESS  read-only
        STATUS      current
        DESCRIPTION
            "The current number of dialogs either in EARLY or CONFIRMED 
             state."
        ::= { kamailioDialogStats 1 }
        
    kamailioCurNumDialogsInProgress     OBJECT-TYPE
        SYNTAX      Gauge32
        MAX-ACCESS  read-only
        STATUS      current
        DESCRIPTION
            "The current number of CONFIRMED dialogs."
        ::= { kamailioDialogStats 2 }
        
    kamailioCurNumDialogsInSetup     OBJECT-TYPE
        SYNTAX      Gauge32
        MAX-ACCESS  read-only
        STATUS      current
        DESCRIPTION
            "The current number of EARLY dialogs."
        ::= { kamailioDialogStats 3 }
        
    kamailioTotalNumFailedDialogSetups     OBJECT-TYPE
        SYNTAX      Counter32
        MAX-ACCESS  read-only
        STATUS      current
        DESCRIPTION
            "The total number of calls that failed with an error. 
             The following codes define a failed call:"
        ::= { kamailioDialogStats 4 }

    kamailioDialogLimitMinorThreshold    OBJECT-TYPE
        SYNTAX      Integer32
        MAX-ACCESS  read-only
        STATUS      current
        DESCRIPTION
            "The configured minor threshold indicating the kamailio system has 
             reached a high level of dialogs. -1 indicates the value
             is not configured, and the alarm will never be set."
        ::= { kamailioDialogStats 5 }

    kamailioDialogLimitMajorThreshold    OBJECT-TYPE
        SYNTAX      Integer32
        MAX-ACCESS  read-only
        STATUS      current
        DESCRIPTION
            "The configured threshold indicating the kamailio system has reached
             a maximum number of dialogs, and perhaps performace will suffer.
             -1 indicates the value is not configured, and alarms will never be 
             set, and the usage state will never be reported as 'busy'."
        ::= { kamailioDialogStats 6 }

    kamailioTotalNumDialogSetups     OBJECT-TYPE
        SYNTAX      Counter32
        MAX-ACCESS  read-only
        STATUS      current
        DESCRIPTION
            "The total number of calls (answered and failed)."
        ::= { kamailioDialogStats 7 }


--
-- Dialog State
--

    kamailioDialogStates  OBJECT-IDENTITY
        STATUS current
        DESCRIPTION
        "a sub-tree for Kamailio's dialog tracking states."
        ::= { kamailioDialog 3 }
    
    kamailioDialogUsageState     OBJECT-TYPE
        SYNTAX      X731UsageState
        MAX-ACCESS  read-only
        STATUS      current
        DESCRIPTION
        "The current usage state of Kamailio's dialog tracking:
            idle(0)   - no dialogs are currently being tracked.
            active(1) - at least 1 dialog is being tracked.
            busy(2)   - the maximum number of dialogs are being tracked.
                        
         The 'busy' point is based on a configuration variable (the same as
         kamailioDialogMajorLimitThreshold): if this value is -1, then the server
         is never considered 'busy'."
    ::= { kamailioDialogStates 1 }

--
-- Dialog Alarms
--
    kamailioDialogAlarms   OBJECT-IDENTITY
        STATUS current
        DESCRIPTION 
        "Sub-tree for call alarms." 
    ::= { kamailioDialog 4 }

    kamailioDialogLimitAlarmStatus  OBJECT-TYPE
        SYNTAX      X731AlarmStatus
        MAX-ACCESS  read-only
        STATUS      current
        DESCRIPTION
           "This alarm status reports the overall alarm status of the dialog
            sub-system. If the thresholds are not configured, then this status
            will always be 'clear'.

            This scalar follows the X731AlarmStatus specs, and can take on
            the following values:
             
            underRepair(0), critical(1), major(2), minor(3), 
            alarmOutstanding(4), unknown(5)"
        ::= { kamailioDialogAlarms 1 }

   kamailioDialogLimitMinorAlarm  OBJECT-TYPE
        SYNTAX      X731AlarmState
        MAX-ACCESS  read-only
        STATUS      current
        DESCRIPTION
           "The Kamailio system is approaching or has reached its configured 
            minor dialog limit threshold.
                clear(0) - the current number of dialogs is below the configured
                           threshold.
                minor(1) - the current number of dialogs has reached or exceeded
                           the configured threshold.
                           
            The threshold is defined in the Kamailio configuration; if it 
             is not configured, this alarm will not be sent."
        ::= { kamailioDialogAlarms 2 }

   kamailioDialogLimitMajorAlarm  OBJECT-TYPE
        SYNTAX      X731AlarmState
        MAX-ACCESS  read-only
        STATUS      current
        DESCRIPTION
           "The Kamailio system is approaching or has reached its configured 
            dialog limit.
                clear(0) - the current number of dialogs is below the configured
                           threshold.
                major(2) - the current number of dialogs has reached or exceeded
                           the configured threshold.
            
            The threshold is defined in the Kamailio configuration; if it 
             is not configured, this alarm will not be sent."
        ::= { kamailioDialogAlarms 3 }

-- 
-- Notifications
--

--
-- This section defines the SNMP traps, or notifications, that the KAMAILIO-MIB
-- supports.
--

    kamailioMIBNotifications  OBJECT-IDENTITY
        STATUS current
        DESCRIPTION 
        "A sub-section for reverse-mapping between SNMPv1 and SNMPv2 events."
        ::= { kamailioMIBEvents 0 } 
        
    kamailioMsgQueueDepthMinorEvent NOTIFICATION-TYPE
        OBJECTS {
          kamailioMsgQueueDepth, kamailioMsgQueueMinorThreshold
        }
        STATUS  current
        DESCRIPTION
        "The message queue depth (as reported by kamailioMsgQueueDepth) has 
         exceeded the minor configured threshold kamailioMsgQueueMinorThreshold."
        ::= { kamailioMIBNotifications 1 }
        
    kamailioMsgQueueDepthMajorEvent NOTIFICATION-TYPE
        OBJECTS {
            kamailioMsgQueueDepth, kamailioMsgQueueMajorThreshold
        }
        STATUS  current
        DESCRIPTION
        "The message queue depth (as reported by kamailioMsgQueueDepth) has 
         exceeded the minor configured threshold kamailioMsgQueueMinorThreshold."
        ::= { kamailioMIBNotifications 2 }
        
    kamailioDialogLimitMinorEvent NOTIFICATION-TYPE
        OBJECTS {
            kamailioCurNumDialogs, kamailioDialogLimitMinorThreshold
        }
        STATUS  current
        DESCRIPTION
        "The number of dialogs being tracked in the system (as reported by
         kamailioCurNumDialogs) has exceeded the minor configured threshold 
         kamailioDialogLimitMinorThreshold."
        ::= { kamailioMIBNotifications 3 }

    kamailioDialogLimitMajorEvent NOTIFICATION-TYPE
        OBJECTS {
            kamailioCurNumDialogs, kamailioDialogLimitMajorThreshold
        }
        STATUS  current
        DESCRIPTION
        "The number of dialogs being tracked in the system (as reported by
         kamailioCurNumDialogs) has exceeded the major configured threshold 
         kamailioDialogLimitMajorThreshold."
        ::= { kamailioMIBNotifications 4 }


--
-- Conformance
--

--
-- Compliance Statements
--
    kamailioCompliance   MODULE-COMPLIANCE
        STATUS      current
        DESCRIPTION
            "The compliance statement for Kamailio in the SOMAvoice product."

        MODULE -- this module
            MANDATORY-GROUPS { kamailioX731Group,
                               kamailioStatsGroup,
                               kamailioAlarmsGroup,
                               kamailioMsgQueueEvents,
                               kamailioDialogLimitEvents }
        ::= { kamailioConform 1 }

    kamailioGroups  OBJECT-IDENTITY
        STATUS current
        DESCRIPTION 
        "Sub-tree for defining the conformance groups."
        ::= { kamailioConform 2 }
        
    kamailioNotifications OBJECT-IDENTITY
        STATUS current
        DESCRIPTION
        "Sub-tree for defining the conformance notifications."
        ::= { kamailioConform 3 }

--
-- Units of Conformance
--
    kamailioX731Group    OBJECT-GROUP
        OBJECTS {
            kamailioDialogUsageState
        }
        STATUS  current
        DESCRIPTION
            "A collection of objects providing X.731 state and alarm status
             information in Kamailio."
        ::= { kamailioGroups 1 }

    kamailioStatsGroup   OBJECT-GROUP
        OBJECTS {
            kamailioMsgQueueDepth,
            kamailioMsgQueueMinorThreshold,
            kamailioMsgQueueMajorThreshold,
            kamailioDialogType,
            kamailioDialogToUri,
            kamailioDialogFromUri,
            kamailioDialogState,
            kamailioDialogStartTime,
            kamailioDialogLastUpdateTime,
            kamailioDialogExpiryTime,
            kamailioCurNumDialogs,
            kamailioCurNumDialogsInProgress,
            kamailioCurNumDialogsInSetup,
            kamailioTotalNumFailedDialogSetups,
            kamailioDialogLimitMinorThreshold,
            kamailioDialogLimitMajorThreshold,
            kamailioTotalNumDialogSetups
        }
        STATUS  current
        DESCRIPTION
            "A collection of objects providing statistics in Kamailio."
        ::= { kamailioGroups 2 }

    kamailioAlarmsGroup   OBJECT-GROUP
        OBJECTS {
            kamailioMsgQueueDepthAlarmStatus,
            kamailioMsgQueueDepthMinorAlarm,
            kamailioMsgQueueDepthMajorAlarm,
            kamailioDialogLimitAlarmStatus,
            kamailioDialogLimitMinorAlarm,
            kamailioDialogLimitMajorAlarm
        }
        STATUS  current
        DESCRIPTION
            "A collection of objects providing stateful alarm information in
             Kamailio."
        ::= { kamailioGroups 3 }
    
    kamailioMsgQueueEvents   NOTIFICATION-GROUP
        NOTIFICATIONS {
            kamailioMsgQueueDepthMinorEvent,
            kamailioMsgQueueDepthMajorEvent
        }
        STATUS current
        DESCRIPTION
            "A collection of events for the message queue depth."
        ::= { kamailioNotifications 1 }

    kamailioDialogLimitEvents   NOTIFICATION-GROUP
        NOTIFICATIONS {
            kamailioDialogLimitMinorEvent,
            kamailioDialogLimitMajorEvent
        }
        STATUS current
        DESCRIPTION
            "A collection of events for dialog tracking."
        ::= { kamailioNotifications 2 }

END

-- vim:ts=4:et:sw=4:si:ai:tw=78
